FME workspace gseFloorplanDerive.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseFP\ETL\serverConfig\GIS Staging.sde   # Connection File
- ProductionConnectionFile = C:\Apps\Gizinta\gseFP\ETL\serverConfig\GIS Production.sde   # Enter the path and name of the Production SDE Database connection file
- GizintaProject = C:\Apps\Gizinta\gseFP\ETL\config\fpDerivePlaylist.xml   # Select the Gizinta Xml File to use
- SourceFieldQA = False   # Choose whether to perform QA on Source Fields
- TargetFieldQA = True   # Choose whether to perform QA on Target Fields
- IgnoreErrors = False   # Ignore Errors and continue
- SourceDatasetTypes = GDBDataset   # Enter the Gizinta Source Dataset Type
- flr = %   # Enter the FloorID or like expression
- gzDebug = False   # Enable gzDebug (True/False)
- LOG_FILE = gseFloorplanDerive.log   # Log File
- FEATURE_TYPES = InteriorSpace_Tilt FloorplanLine InteriorSpace Floor_Outline Floor_Point Floor_Poly FloorplanLine_Publish Floor_Area InteriorSpace_Point   # Feature Types to Write
- FEATURE_TYPES_READ = Floor_Poly InteriorSpace FloorplanLine
- SourceDataset_GEODATABASE_SDE = sde   # Source Esri ArcSDE Geodatabase Dataset
- FEATURE_TYPES_PROD = Building_Outline_Point Building_Outline_Tilt Active_Floor Floor_Level
- truncate = Y   # Truncate before load option
- elevName = schelev   # Floor Elevation Value Name

Readers:
- GEODATABASE_SDE_1: GEODATABASE_SDE from $(DestDataset_GEODATABASE_SDE)
- GEODATABASE_SDE_2: GEODATABASE_SDE from $(DestDataset_GEODATABASE_SDE)
- GEODATABASE_SDE_3: GEODATABASE_SDE from $(SourceDataset_GEODATABASE_SDE)

Writers:
- GEODATABASE_SDE_4: GEODATABASE_SDE to $(DestDataset_GEODATABASE_SDE)

DBO.Floor_Area (reader GEODATABASE_SDE_2)
    attributes: geodb_oid integer, OBJECTID integer, SITEID char(60), BUILDINGID char(60), FLOOR char(20), FLOORID char(60), FLOOR_AREA double, SCHELEV smallint, ALTITUDE smallint, SENSITIVITY char(20), SOURCEDWG char(60), IN_DATE date, LAST_USER char(30), GlobalID char(38), FLOOR_NAME char(60), BLDG_NAME char(60), SHAPE.STArea() double, SHAPE.STLength() double
    -> AttributeExposer_2
AttributeExposer_2
    ATTR_LIST = fme_feature_type,SPACEID,FLOORID,FLOORAREA
    -> TestFeatureTypes
TestFeatureTypes: Tester
    TEST_MODE = Automatic
    TEST_DESCRIPTION = ""
    BOOL_OP = OR
    TEST_CLAUSE = TEST $(FEATURE_TYPES_READ) CONTAINS @Value(fme_feature_type)
    PASSED -> BulkAttributeRenamer_2
BulkAttributeRenamer_2
    CASE_CHANGE_TYPE = lowercase
    ATTRCHOICE = All Attributes
    PATTERN_ACTION_DISP = Change Case
    -> FeatureMerger [input 1]
Building_Outline_Point (reader GEODATABASE_SDE_3)
    attributes: geodb_oid integer, OBJECTID integer, SITEID char(60), BUILDINGID char(60), CALCROT double, NUMFLOORS integer, SOURCEDWG char(60), SCALE_85X11 double, SCALE_11X17 double, SENSITIVITY char(20), IN_DATE date, LAST_USER char(30), GlobalID char(38), ALTITUDE double, SOURCEID char(30), DWG_NAME char(255), FLOOR char(6), INTERIORSPACE char(255), NAME_LONG char(255), BLDGHEIGHT double, FLOOR_LEVEL integer, SCHELEV integer, SHAPE.STLength() double, MARGIN double, FLOORPLANLINE char(255), YCENTER double, SHAPE.STArea() double, XCENTER double, FLOORID char(20), SPACING double,
      NAME_SHORT char(255)
    -> AttributeExposer_3
AttributeExposer_3
    ATTR_LIST = fme_feature_type,BUILDINGID,FLOORID
    -> BulkAttributeRenamer
BulkAttributeRenamer
    CASE_CHANGE_TYPE = lowercase
    ATTRCHOICE = All Attributes
    PATTERN_ACTION_DISP = Change Case
    -> gseGetBldgFloorInfo
gseGetBldgFloorInfo
    FLOOR = @Value(floor)
    FLOOR_LEVEL = @Value(floor_level)
    BUILDINGID = @Value(buildingid)
    FeatureMerger_3_Merged -> FeatureMerger [input 2]
FeatureMerger
    PROCESS_DUPS = No
    MERGE_TYPE = Attributes Only
    SUPPLIERS_FIRST = No
    JOIN_KEYS = @Value(floorid) @Value(floorid) AUTO
    SUPPLIER_PREFIX_DUMMY = YES
    MERGED -> TestFilter
    NOT_MERGED -> FeatureMerger_NotMerged_2
TestFilter
    TEST_LIST = BOOL_OP,OR,COMPOSITE_TEST,<Unused>,TEST_CLAUSE,"TEST @Value(fme_feature_type) = FloorplanLine",FloorplanLine,BOOL_OP,OR,COMPOSITE_TEST,<Unused>,TEST_CLAUSE,"TEST @Value(fme_feature_type) = Floor_Poly",Floor_Poly,BOOL_OP,OR,COMPOSITE_TEST,<Unused>,TEST_CLAUSE,"TEST @Value(fme_feature_type) = InteriorSpace",InteriorSpace
    DEFAULT_VALUE = <UNFILTERED>
    FloorplanLine -> HullAccumulator
    Floor_Poly -> Aggregator
    Floor_Poly -> FeatureMerger_2 [input 2]
    InteriorSpace -> gzTiltRooms
    InteriorSpace -> InsidePointReplacer
    FloorplanLine -> AttributeExposer
Note: Create Floor_Outline polygon
HullAccumulator
    GROUP_BY = floorid
    HULLTYPE_PARAM = Convex ()
    HULL -> Bufferer
Bufferer
    GROUP_BY = floorid
    INTERP_SEGMENTS = 8
    OFFSET = 1
    CAP_STYLE = Round
    BUFFERED -> FeatureMerger_2 [input 1]
AttributeExposer
    ATTR_LIST = fme_type,fme_geometry
    -> FeatureMerger_2 [input 2]
FeatureMerger_2
    PROCESS_DUPS = No
    MERGE_TYPE = Attributes Only
    SUPPLIERS_FIRST = No
    JOIN_KEYS = @Value(floorid) @Value(floorid) AUTO
    SUPPLIER_PREFIX_DUMMY = YES
    MERGED -> Floor_Outline
Floor_Outline: AttributeCreator
    ATTR_LIST = fme_feature_type,Floor_Outline
    -> AttributeCreator_3
Aggregator
    GROUP_BY = floorid
    MODE = Assemble One Level
    ACCUM_ATTRS_NAME = Yes
    SEP = ,
    SUM = floorarea
    AGGREGATE_TYPE = Homogeneous Collection (If Possible)
    ORDERED = No
    AGGREGATE -> Floor_Area
    AGGREGATE -> GeometryReplacer
Note: Create floorpoint using Outline center point
GeometryReplacer
    SOURCE = @Value(_geometry)
    REMOVE_ATTRIBUTE = Yes
    KIND_LONG = FME Binary
    -> Floor_Point
Floor_Point: AttributeCreator
    ATTR_LIST = fme_feature_type,Floor_Point
    -> AttributeCreator_3
Floor_Area: AttributeCreator
    ATTR_LIST = fme_feature_type,Floor_Area
    -> AttributeCreator_3
Note: Create Floor_Area Aggregate Polygon
gzTiltRooms
    CALCROT = @Value(calcrot)
    MARGIN = .1
    _XMAX = @Value(_xmax)
    SPACEID = @Value(spaceid)
    _YMAX = @Value(_ymax)
    tiltDemoninator = 2
    SPACING = 1
    _YMIN = @Value(_ymin)
    STACKLEVEL = @Value(stacklevel)
    -> InteriorSpace_Tilt
InteriorSpace_Tilt: AttributeCreator
    ATTR_LIST = fme_feature_type,InteriorSpace_Tilt
    -> AttributeCreator_3
Note: Tilt function for interior spaces
Note: Create points for Spaces
InsidePointReplacer
    INSIDEPOINT -> InteriorSpace_Point
InteriorSpace_Point: AttributeCreator
    ATTR_LIST = fme_feature_type,InteriorSpace_Point
    -> AttributeCreator_3
AttributeCreator_3
    ATTR_LIST = DRAWING,@Value(floorid)
    -> 3DForcer
3DForcer
    ZVALATTR = @Value($(elevName)) * 0.3048
    -> BulkAttributeRenamer_3
Note: SQL Server/Oracle
BulkAttributeRenamer_3
    CASE_CHANGE_TYPE = UPPERCASE
    ATTRCHOICE = All Attributes
    PATTERN_ACTION_DISP = Change Case
    -> gzFieldCalculator
gzFieldCalculator
    AddFieldsValues_Output_1 -> gzSourceTargetQA
gzSourceTargetQA
    SourceTargetQA_Output_1 -> gzWriteData
gzWriteData
    IgnoreErrors = False
    GroupBy = @Value(FLOORID)
    HASERRORS = @Value(HasErrors)
    gzLogWriter -> gzLog (writer GEODATABASE_SDE_4)
    gzErrorWriter -> gzError (writer GEODATABASE_SDE_4)
    gzFeatureWriter -> TruncateFirst
gzLog (writer GEODATABASE_SDE_4)
    attributes: procname char(255), loadtime date, loadname char(255), dataset char(255), completed smallint, loaduser char(255), activeflag char(255)
TruncateFirst: TestFilter
    TEST_LIST = BOOL_OP,OR,COMPOSITE_TEST,<Unused>,TEST_CLAUSE,"TEST $(truncate) = Y",Y,BOOL_OP,OR,COMPOSITE_TEST,<Unused>,TEST_CLAUSE,"TEST $(truncate) = N",N
    DEFAULT_VALUE = <UNFILTERED>
    N -> NewFeatureType (writer GEODATABASE_SDE_4)
    Y -> NewFeatureType00 (writer GEODATABASE_SDE_4)
NewFeatureType00 (writer GEODATABASE_SDE_4)
NewFeatureType (writer GEODATABASE_SDE_4)
gzError (writer GEODATABASE_SDE_4)
    attributes: procname char(255), sourcename char(255), srcidfield char(255), srcidval char(255), dataset char(255), reason char(255), erruser char(255), errtime date, activeflag char(255)
FeatureMerger_NotMerged_2: Logger
    MESSAGE = Feature is missing floor data:
    MAXFEATS = 20000
    MAXCOORDS = 20

FME custom transformer gseGetBldgFloorInfo

Parameters:
- flr =   # Floor ID
- BUILDINGID = @Value(buildingid)   # buildingid
- FLOOR = @Value(floor)   # floor
- FLOOR_LEVEL = @Value(floor_level)   # Floor Level

TestFilter_2_Input (input)
    -> AttributeExposer
AttributeExposer
    ATTR_LIST = floorid,buildingid,bldg,schelev,fme_feature_type,floor,siteid,calcrot,floor_name,floor_level
    -> TestFilter_2
TestFilter_2
    TEST_LIST = BOOL_OP,OR,COMPOSITE_TEST,<Unused>,TEST_CLAUSE,"TEST @Value(fme_feature_type) = Building_Outline_Tilt",Building_Outline_Tilt,BOOL_OP,OR,COMPOSITE_TEST,<Unused>,TEST_CLAUSE,"TEST @Value(fme_feature_type) = Building_Outline_Point",Building_Outline_Point,BOOL_OP,OR,COMPOSITE_TEST,<Unused>,TEST_CLAUSE,"TEST @Value(fme_feature_type) = Active_Floor",Active_Floor,BOOL_OP,OR,COMPOSITE_TEST,<Unused>,TEST_CLAUSE,"TEST @Value(fme_feature_type) = Floor_Level",Floor_Level
    DEFAULT_VALUE = <UNFILTERED>
    Floor_Level -> FeatureMerger_3 [input 2]
    Building_Outline_Tilt -> BoundsExtractor
    Building_Outline_Point -> GeometryExtractor
    Active_Floor -> ListBuilder_2
BoundsExtractor
    YMIN = _ymin
    ZMIN = _zmin
    XMIN = _xmin
    XMAX = _xmax
    ZMAX = _zmax
    YMAX = _ymax
    -> LengthCalculator
LengthCalculator
    LEN_ATTR = _bldg_outline_length
    MULT = 1
    DIM = 2
    -> FeatureMerger_4 [input 1]
GeometryExtractor
    ATTR = _geometry
    KIND_LONG = FME Binary
    -> FeatureMerger_4 [input 2]
FeatureMerger_4
    PROCESS_DUPS = No
    MERGE_TYPE = Attributes Only
    SUPPLIERS_FIRST = No
    JOIN_KEYS = @Value(buildingid) @Value(buildingid) AUTO
    SUPPLIER_PREFIX_DUMMY = YES
    MERGED -> FeatureMerger_5 [input 1]
ListBuilder_2
    LIST_NAME = _floors
    GRP_BY = buildingid
    -> sortScheleve
sortScheleve: ListSorter
    TYPE = Numeric
    SRC_LIST = _floors{}.schelev
    ORDER = Increasing
    -> ListExploder_2
ListExploder_2
    INDEX_ATTR = _stack_index
    MODE = List Elements and Original Attributes
    LIST_ATTR = _floors{}
    LIST_FOUND -> AttributeCopier
AttributeCopier
    ATTR_LIST = _stack_index,stacklevel,""
    -> FeatureMerger_5 [input 2]
FeatureMerger_5
    PROCESS_DUPS = Yes
    MERGE_TYPE = Attributes Only
    LIST_NAME = _flrs
    GEOM_TYPE = Build Polygons
    SUPPLIERS_FIRST = No
    JOIN_KEYS = @Value(buildingid) @Value(buildingid) AUTO
    SUPPLIER_PREFIX_DUMMY = YES
    MERGED -> ListExploder
ListExploder
    INDEX_ATTR = _element_index
    MODE = List Elements and Original Attributes
    LIST_ATTR = _flrs{}
    LIST_FOUND -> FeatureMerger_3 [input 1]
FeatureMerger_3
    PROCESS_DUPS = No
    MERGE_TYPE = Attributes Only
    SUPPLIERS_FIRST = No
    JOIN_KEYS = @Value(floor) @Value(floor) AUTO
    SUPPLIER_PREFIX_DUMMY = YES
    MERGED -> FeatureMerger_3_Merged (output)
FeatureMerger_3_Merged (output)

FME custom transformer gzTiltRooms
Tilt Rooms in floorplans to create a pseudo-isometric view of the rooms and floors

Parameters:
- _XMAX = @Value(_xmax)   # Xmax
- _YMAX = @Value(_ymax)   # Ymax
- _YMIN = @Value(_ymin)   # Ymin
- tiltDemoninator = 2   # Tilt = 2 will tilt 50% or y/2
- STACKLEVEL = @Value(stacklevel)   # stacklevel
- CALCROT = @Value(calcrot)   # calcrot
- SPACEID = @Value(spaceid)   # spaceid
- MARGIN = .1   # margin
- SPACING = 1   # spacing

INPUT (input)
    -> Rotation
Note: Function will rotate flat/horizontal. Add 15 degrees
Rotation: ExpressionEvaluator
    VAL_ATTR = calculated_rotation
    EXPRESSION = @Value(calcrot) + 15
    -> Rotator
Rotator
    YORIG = @Value(_ymax)
    ANGLE = @Value(calculated_rotation)
    XORIG = @Value(_xmax)
    ROTATED -> Y_Base
Note: Add 10 meters to the base of every point * stacklevel + y height
Y_Base: ExpressionEvaluator
    VAL_ATTR = _yBase
    EXPRESSION = (@Value(_ymax)  + 10 ) + (@Value(stacklevel)  * $(SPACING) * (@abs(@Value(_ymax) - @Value(_ymin))/$(tiltDemoninator)))
    -> tiltFactor
tiltFactor: ExpressionEvaluator
    VAL_ATTR = _tiltFactor
    EXPRESSION = "$(SPACING) * $(tiltDemoninator)\n\n"
    -> AttributeCreator
AttributeCreator
    ATTR_LIST = _subtracty,@Value(_ymax),_margin,$(MARGIN)
    -> TiltFeatures
TiltFeatures: PythonCaller
    PYTHONSOURCE:
      import fmeobjects

      debug = False
      # Template Function interface:
      def processFeature(feature):
          pass

      # Template Class Interface:
      class FeatureProcessor(object):
          def __init__(self):
              pass
          def input(self,feature):
              ### Formula is yBase + ((y - subtracty) / tiltFactor) * (1 - margin)
              yBase = float(feature.getAttribute("_yBase"))
              subtracty = float(feature.getAttribute("_subtracty"))
              tiltFactor = float(feature.getAttribute("_tiltFactor"))
              margin = float(feature.getAttribute("_margin"))
              heightPercent = 1 - margin
              if debug == True:
                  logger.logMessageString(str(yBase) + '|' + str(subtracty) + '|' +  str(tiltFactor) + '|' +  str(margin))
              parts = feature.getDonutParts()
              for part in parts:
                  coords = part.getAllCoordinates()
                  for i in xrange(len(coords)):
                      # Assume 2D geometries here
                      y = coords[i][1]
                      yDiff = y - subtracty
                      rawY = yDiff / tiltFactor
                      addY = rawY * heightPercent
                      tilt_y = yBase + addY
                      coords[i] = (coords[i][0], tilt_y)

                      if debug == True:
                          logger.logMessageString("y="+str(y))
                          logger.logMessageString("yBase="+str(yBase))
                          logger.logMessageString("rawY="+str(rawY))
                          #logger.logMessageString("yDiff="+str(yDiff))
                          #logger.logMessageString("heightPercent="+str(heightPercent))
                          #logger.logMessageString("tiltFactor="+str(tiltFactor))
                          logger.logMessageString("addY="+str(addY))
                          logger.logMessageString("tilt_y="+str(tilt_y))
                  part.resetCoords()
                  part.addCoordinates(coords)
              if len(parts) > 0:
                  feature.makeDonuts(parts)
                  del coords, parts
              self.pyoutput(feature)

          def close(self):
              pass
    PYTHONSYMBOL = FeatureProcessor
    NEW_ATTRIBUTES = _subtracty _yBase margin _tiltFactor
    -> GeometryValidator_3
GeometryValidator_3
    CHECK_HOLE_TOUCHING_POLYGON = Yes
    DUP_COORDS_CHECK_Z = Yes
    PLANAR_TOLERANCE = 0.001
    TYPE_REPAIR = TYPE_REPAIR
    SELF_INTERSECTING = SELF_INTERSECTING
    PRESETS = Custom
    ARC_ENDPOINT_TOLERANCE_MODE = Custom
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = No
    ISSUE_ATTR_NAME = _issues
    ARC_ENDPOINT_TOLERANCE = 0.001
    PLANAR_TOLERANCE_MODE = Custom
    CONSECUTIVE_IDENTICAL_VERTICES_2D = CONSECUTIVE_IDENTICAL_VERTICES_2D
    FAILED -> Generalizer
    PASSED -> OUTPUT (output)
Generalizer
    ALG_TEXT = Douglas (Generalize)
    PRESERVE = No
    TOLERANCE = .05
    -> SpikeRemover
SpikeRemover
    SPIKEANGLE = 3
    UNCHANGED -> GeometryValidator_2
    CHANGED -> GeometryValidator_2
GeometryValidator_2
    CHECK_HOLE_TOUCHING_POLYGON = Yes
    DUP_COORDS_CHECK_Z = No
    SELF_INTERSECTING = SELF_INTERSECTING
    PRESETS = Custom
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    ISSUE_ATTR_NAME = _issues
    CONSECUTIVE_IDENTICAL_VERTICES_2D = CONSECUTIVE_IDENTICAL_VERTICES_2D
    PASSED -> OUTPUT (output)
    REPAIRED -> OUTPUT (output)
    FAILED -> GeometryValidator_2_Failed
OUTPUT (output)
GeometryValidator_2_Failed: Logger
    MESSAGE = Feature is:
    MAXFEATS = 20
    MAXCOORDS = 20

FME custom transformer gzSetupExtract

INPUT (input)
    -> AttributeExposer
AttributeExposer
    ATTR_LIST = fme_feature_type_name
    -> PythonCaller
PythonCaller
    PYTHONSOURCE:
      import fmeobjects


      # Template Function interface:
      def processFeature(feature):
          pass

      # Template Class Interface:
      class FeatureProcessor(object):
          def __init__(self):
              pass
          def input(self,feature):
              whereClause = ""
              featType = feature.getAttribute("fme_feature_type_name")
              for sourceDataset in sourceDatasets:
                  sourceName = sourceDataset.getAttributeNode("sourceName").nodeValue
                  if debug == True:
                      logger.logMessageString("gz sources=" + featType + "|" + sourceName)
                  if sourceName == featType:
                      whereClause = getWhereClause(featType)
                      if debug == True:
                          logger.logMessageString("gz Where=" + whereClause)
                      feature.setAttribute("WhereClause",whereClause)
                      self.pyoutput(feature)

          def close(self):
              pass
    PYTHONSYMBOL = FeatureProcessor
    NEW_ATTRIBUTES = WhereClause *
    -> OUTPUT (output)
OUTPUT (output)

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    LEN_ATTR = _length
    MULT = 1
    DIM = 2
    -> StatisticsCalculator_2
StatisticsCalculator_2
    STATS_ATTR = _length
    PASS_THROUGH = Yes
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    X_ATTR = _x1
    Z_DEFAULT = -9999
    Z_ATTR = _z
    IND = 0
    -> CoordinateExtractor_6
CoordinateExtractor_6
    Y_ATTR = _y2
    X_ATTR = _x2
    Z_DEFAULT = -9999
    Z_ATTR = _z
    IND = 1
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    BUILD_INCOMPLETE = No
    PROCESS_DUPS = No
    MERGE_TYPE = Attributes Only
    REFERATTR = $(BUILDINGID)
    REFEEATTR = $(BUILDINGID)
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Y_ATTR = YCENTER
    X_ATTR = XCENTER
    Z_DEFAULT = -9999
    Z_ATTR = _z
    IND = 0
    -> GeometryReplacer
GeometryReplacer
    ATTR = _geometry
    KIND_LONG = FME Binary
    -> AttributeCreator
Note: Calculate X and Y Center Point
AttributeCreator
    ATTR_LIST = MODANGLE,0,SPACING,50,MARGIN,.2,HULLROT,@Value(_angle)
    -> OUTPUT (output)
OUTPUT (output)
