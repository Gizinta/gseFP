FME workspace gseBuildingOutlineLoader.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseFP\ETL\serverConfig\GIS Staging.sde   # Connection File
- GizintaProject = C:\Apps\Gizinta\gseFP\ETL\config\bldgOutlinePlaylist.xml   # Select the Gizinta Xml File to use
- SourceFieldQA = False   # Choose whether to perform QA on Source Fields
- TargetFieldQA = True   # Choose whether to perform QA on Target Fields
- IgnoreErrors = False   # Ignore Errors and continue
- SourceDatasetTypes = CADDataset   # Enter the Gizinta Source Dataset Type
- gzDebug = False   # Enable gzDebug (True/False)
- LOG_FILE =   # Log File
- SourceCoordinateSystem = EPSG:2285   # Source Coordinate System
- SourceDataset_ESRIMSD = C:\Apps\Gizinta\gseFP\**\*Outline.dwg   # Source Autodesk AutoCAD DWG/DXF File(s)
- FEATURE_TYPES_READ = Building_Outline_Tilt   # Feature Types to Read
- FEATURE_TYPES = Building_Outline_Tilt Building_Outline_Point   # Feature Types to Write

Readers:
- ESRIMSD_1: ESRIMSD from $(SourceDataset_ESRIMSD)
- GEODATABASE_SDE_1: GEODATABASE_SDE from $(DestDataset_GEODATABASE_SDE)

Writers:
- GEODATABASE_SDE_2: GEODATABASE_SDE to $(DestDataset_GEODATABASE_SDE)

Building_Roof (reader ESRIMSD_1)
    attributes: FACNUM char(254)
    -> AttributeExposer
AttributeExposer
    ATTR_LIST = fme_basename,fme_feature_type,FACNUM,autocad_source_filename
    -> Tester
Tester
    TEST_MODE = Automatic
    TEST_DESCRIPTION = ""
    BOOL_OP = OR
    TEST_CLAUSE = TEST $(FEATURE_TYPES_READ) CONTAINS @Value(fme_feature_type)
    PASSED -> gzFieldCalculator
gzFieldCalculator
    AddFieldsValues_Output_1 -> Reprojector
Reprojector
    DEST = EPSG:3857
    RASTER_CELL_SIZE = Preserve Cells
    STROKE_ARCS = Yes
    SOURCE = $(SourceCoordinateSystem)
    INTERPOLATION_TYPE_NAME = Nearest Neighbor
    REPROJECTED -> TestFilter_2
TestFilter_2
    TEST_LIST = BOOL_OP,OR,COMPOSITE_TEST,<Unused>,TEST_CLAUSE,"TEST @Value(fme_feature_type) = Building_Outline_Tilt",Building_Outline,BOOL_OP,OR,COMPOSITE_TEST,<Unused>,TEST_CLAUSE,"TEST @Value(fme_feature_type) = Building_Outline_Point",Building_Outline_Point
    DEFAULT_VALUE = <UNFILTERED>
    Building_Outline -> bldg
Note: Special Calculations for Outline attributes
bldg: AttributeExposer
    ATTR_LIST = BUILDINGID
    -> gzBuildingOutlineTilt
gzBuildingOutlineTilt
    BUILDINGID = @Value(BUILDINGID)
    -> CenterPointReplacer
    -> gzSourceTargetQA
CenterPointReplacer
    CENTERPOINT -> AttributeCreator
AttributeCreator
    ATTR_LIST = fme_feature_type,Building_Outline_Point
    -> gzSourceTargetQA
gzSourceTargetQA
    SourceTargetQA_Output_1 -> DuplicateRemover
DuplicateRemover
    KEYATTR = autocad_entity_handle fme_feature_type
    UNIQUE -> gzWriteData
gzWriteData
    IgnoreErrors = $(IgnoreErrors)
    GroupBy = @Value(BUILDINGID)
    HASERRORS = @Value(HasErrors)
    gzLogWriter -> gzLog (writer GEODATABASE_SDE_2)
    gzErrorWriter -> gzError (writer GEODATABASE_SDE_2)
    gzFeatureWriter -> DBO.Building_Outline_Tilt (writer GEODATABASE_SDE_2)
gzLog (writer GEODATABASE_SDE_2)
    attributes: PROCNAME char(255), LOADTIME date, LOADNAME char(255), DATASET char(255), COMPLETED smallint, LOADUSER char(255), ACTIVEFLAG char(255)
DBO.Building_Outline_Tilt (writer GEODATABASE_SDE_2)
    attributes: geodb_oid integer, OBJECTID integer, SITEID char(60), BUILDINGID char(60), CALCROT double, SOURCEID char(30), SOURCEDWG char(60), LASTUPDATE date, LASTEDITOR char(30), BLDGNAME char(100), SHAPE.STArea() double, SHAPE.STLength() double
gzError (writer GEODATABASE_SDE_2)
    attributes: PROCNAME char(255), SOURCENAME char(255), SRCIDFIELD char(255), SRCIDVAL char(255), DATASET char(255), REASON char(255), ERRUSER char(255), ERRTIME date, ACTIVEFLAG char(255)

FME custom transformer gzBuildingOutline

Parameters:
- BUILDINGID = @Value(BUILDINGID)

INPUT (input)
    -> Chopper_2
    -> FeatureMerger_3 [input 1]
Chopper_2
    MAX = 2
    CHOPPED -> LengthCalculator_2
LengthCalculator_2
    LEN_ATTR = _length
    MULT = 1
    DIM = 2
    -> StatisticsCalculator_2
StatisticsCalculator_2
    GROUP_BY = BUILDINGID
    STATS_ATTR = _length
    PASS_THROUGH = Yes
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    X_ATTR = _x1
    Z_DEFAULT = -9999
    Z_ATTR = _z
    IND = 0
    -> CoordinateExtractor_6
CoordinateExtractor_6
    Y_ATTR = _y2
    X_ATTR = _x2
    Z_DEFAULT = -9999
    Z_ATTR = _z
    IND = 1
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    BUILD_INCOMPLETE = No
    PROCESS_DUPS = No
    MERGE_TYPE = Attributes Only
    REFERATTR = BUILDINGID
    REFEEATTR = BUILDINGID
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Y_ATTR = YCENTER
    X_ATTR = XCENTER
    Z_DEFAULT = -9999
    Z_ATTR = _z
    IND = 0
    -> GeometryReplacer
GeometryReplacer
    ATTR = _geometry
    KIND_LONG = FME Binary
    -> AttributeCreator
Note: Calculate X and Y Center Point
AttributeCreator
    ATTR_LIST = BLDGHEIGHT,@Evaluate( abs(@Value(_y2) - @Value(_y1)) ),CALCROT,@Value(_angle)
    -> OUTPUT (output)
OUTPUT (output)

FME custom transformer gzTiltRooms
Tilt Rooms in floorplans to create a pseudo-isometric view of the rooms and floors

Parameters:
- pFACNUM =   # Enter the Building Identifier
- pFacFloor =   # Enter the FacFloor Number

INPUT (input)
    -> DuplicateRemover
    -> FeatureMerger_2 [input 1]
    -> DuplicateRemover_2
DuplicateRemover_2
    KEYATTR = $(pFACNUM)
    UNIQUE -> BldgReader
BldgReader: FeatureReader
    GEODATABASE_SDE_RESOLVE_SUBTYPE_NAMES = yes
    GEODATABASE_SDE_SPLIT_COMPLEX_EDGES = no
    FEATURETYPES = DBO.Building_Outline
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = Keep result attributes only
    GEODATABASE_SDE_REMOVE_TABLE_QUALIFIER = NO
    GEODATABASE_SDE_IGNORE_RELATIONSHIP_INFO = yes
    GEODATABASE_SDE_WHERE = FACNUM=@Value(FACNUM)
    SUPPORTED_SPATIAL_INTERACTIONS = ENVELOPE_INTERSECT%ENVELOPE_INTERSECT%INTERSECTS%CONTAINS%CROSSES%DISJOINT%EQUALS%OVERLAPS%TOUCHES%WITHIN
    DATASET = sde
    GEODATABASE_SDE_TABLELIST = DBO.Building_Outline
    GEODATABASE_SDE_SPLIT_MULTI_PART_ANNOS = no
    ATTRIBUTES = DBO.Building_Outline,"geodb_oid,OBJECTID,FACNUM,HULLROT,BLDGHEIGHT,MODANGLE,SPACING,MARGIN,XCENTER,YCENTER,SHAPE.STArea(),SHAPE.STLength()"
    GEODATABASE_SDE_RESOLVE_DOMAINS = no
    FORMAT = GEODATABASE_SDE
    GEODATABASE_SDE_CONNECTION_FILE = $(FME_MF_DIR)GIS Production.sde
    GEODATABASE_SDE_IGNORE_NETWORK_INFO = yes
    DBO.Building_Outline -> BoundsExtractor_2
BoundsExtractor_2
    YMIN = _ymin
    ZMIN = _zmin
    XMIN = _xmin
    XMAX = _xmax
    ZMAX = _zmax
    YMAX = _ymax
    -> FeatureMerger_2 [input 2]
FeatureMerger_2
    PROCESS_DUPS = No
    MERGE_TYPE = Attributes Only
    SUPPLIERS_FIRST = No
    JOIN_KEYS = @Value(FACNUM) @Value(FACNUM)
    SUPPLIER_PREFIX_DUMMY = YES
    MERGED -> FeatureMerger_3 [input 1]
DuplicateRemover
    KEYATTR = $(pFACNUM)
    UNIQUE -> FloorsReader
FloorsReader: FeatureReader
    GEODATABASE_SDE_RESOLVE_SUBTYPE_NAMES = yes
    GEODATABASE_SDE_SPLIT_COMPLEX_EDGES = no
    FEATURETYPES = DBO.Active_Floor
    GEODATABASE_SDE_VERSION = SDE.DEFAULT
    GEODATABASE_SDE_TRANSLATE_SPATIAL_DATA_ONLY = no
    GEODATABASE_SDE_CONNECTION = Connection File
    COMBINE_GEOM = In case of conflict, keep aggregate of INITIATOR and result geometry
    GEODATABASE_SDE_VERSION_TYPE = Connect using a Transactional Version
    COMBINE_ATTRS = In case of conflict, keep result attributes
    GEODATABASE_SDE_REMOVE_TABLE_QUALIFIER = NO
    GEODATABASE_SDE_IGNORE_RELATIONSHIP_INFO = yes
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.Active_Floor
    GEODATABASE_SDE_SPLIT_MULTI_PART_ANNOS = no
    ATTRIBUTES = DBO.Active_Floor,"geodb_oid,OBJECTID,FACNUM,FLOOR,FACFLOOR,DWG_NAME,INTERIORSPACE,FLOORPLANLINE,SCHELEV,ALTITUDE,GlobalID"
    GEODATABASE_SDE_RESOLVE_DOMAINS = no
    FORMAT = GEODATABASE_SDE
    GEODATABASE_SDE_CONNECTION_FILE = $(FME_MF_DIR)GIS Production.sde
    GEODATABASE_SDE_IGNORE_NETWORK_INFO = yes
    DBO.Active_Floor -> AttributeCopier_3
AttributeCopier_3
    ATTR_LIST = STACKLEVEL,SCHELEV
    -> FeatureMerger_3 [input 2]
FeatureMerger_3
    PROCESS_DUPS = No
    MERGE_TYPE = Attributes Only
    SUPPLIERS_FIRST = No
    JOIN_KEYS = @Value(FACFLOOR) @Value(FACFLOOR)
    SUPPLIER_PREFIX_DUMMY = YES
    MERGED -> ExpressionEvaluator_2
ExpressionEvaluator_2
    VAL_ATTR = CALCULATED_ROTATION
    EXPRESSION = @Value(MODANGLE) + @Value(HULLROT) + 15.0
    -> Rotator
Rotator
    YORIG = 0
    ANGLE = @Value(CALCULATED_ROTATION)
    XORIG = 0
    ROTATED -> Y_Base
Y_Base: ExpressionEvaluator
    VAL_ATTR = _yBase
    EXPRESSION = @Value(_ymin) + (@Value(SPACING) * @Value(STACKLEVEL))
    -> tilt_Space
tilt_Space: ExpressionEvaluator
    VAL_ATTR = _tiltSpace
    EXPRESSION = @Value(BLDGHEIGHT) / (@Value(SPACING)+0.00001)
    -> Chopper
Chopper
    MAX = 1
    CHOPPED -> CoordinateExtractor
CoordinateExtractor
    Y_ATTR = _y
    X_ATTR = _x
    Z_DEFAULT = -9999
    Z_ATTR = _z
    IND = 0
    -> tilt_y
tilt_y: ExpressionEvaluator
    VAL_ATTR = _tiltY
    EXPRESSION = @Value(_yBase) + ((@Value(_y) - @Value(_ymin)) / @Value(_tiltSpace)) * (1 - @Value(MARGIN))
    -> 2DPointReplacer
2DPointReplacer
    XVALATTR = @Value(_x)
    YVALATTR = @Value(_tiltY)
    POINT -> PointConnector
PointConnector
    BREAKATTR = FACROOM
    POLYGON -> GeometryCoercer_2
    LINE -> GeometryCoercer_2
GeometryCoercer_2
    CHECKZ = No
    KIND = fme_polygon
    COERCED -> SliverRemover_2
SliverRemover_2
    REPAIR_METHOD = Longest Boundary
    REPAIRED -> SelfIntersectChecker_4
SelfIntersectChecker_4
    NotSelfIntersecting -> OUTPUT (output)
OUTPUT (output)

FME custom transformer gzCalculateRotation

Parameters:
- SourceCoordinateSystem = EPSG:2285   # Source Coordinate System

INPUT (input)
    -> AttributeCreator_7
AttributeCreator_7
    ATTR_LIST = WORLD,World
    -> AttributeFilter
AttributeFilter
    ATTR_NAME = text_line_number
    ATTR_VALUES = <BLANK>,<UNFILTERED>,1,2
    2 -> AttributeSplitter2
    1 -> AttributeSplitter1
AttributeSplitter1
    LIST_NAME = _pts
    ATTR_NAME = text_line_data
    DELIMITER = " "
    TRIM_OPTION = None
    DROP_EMPTY_PARTS = No
    -> AttributeSplitter_1
    -> AttributeSplitter_2
AttributeSplitter_1
    LIST_NAME = _pt
    ATTR_NAME = _pts{0}
    DELIMITER = ,
    TRIM_OPTION = Both
    DROP_EMPTY_PARTS = No
    -> AttributeCreator_1
AttributeCreator_1
    ATTR_LIST = x1,@Value(_pt{0}),y1,@Value(_pt{1})
    -> 2DPointAdder_1
2DPointAdder_1
    XVALATTR = @Value(x1)
    YVALATTR = @Value(y1)
    -> PointConnector
AttributeSplitter_2
    LIST_NAME = _pt2
    ATTR_NAME = _pts{1}
    DELIMITER = ,
    TRIM_OPTION = Both
    DROP_EMPTY_PARTS = No
    -> AttributeCreator_2
AttributeCreator_2
    ATTR_LIST = x2,@Value(_pt2{0}),y2,@Value(_pt2{1})
    -> 2DPointAdder_2
2DPointAdder_2
    XVALATTR = @Value(x2)
    YVALATTR = @Value(y2)
    -> PointConnector_2
AttributeSplitter2
    LIST_NAME = _pts
    ATTR_NAME = text_line_data
    DELIMITER = " "
    TRIM_OPTION = None
    DROP_EMPTY_PARTS = No
    -> AttributeSplitter_4
    -> AttributeSplitter_3
AttributeSplitter_3
    LIST_NAME = _pt
    ATTR_NAME = _pts{0}
    DELIMITER = ,
    TRIM_OPTION = Both
    DROP_EMPTY_PARTS = No
    -> AttributeCreator_3
AttributeCreator_3
    ATTR_LIST = x3,@Value(_pt{0}),y3,@Value(_pt{1})
    -> 2DPointAdder_3
2DPointAdder_3
    XVALATTR = @Value(x3)
    YVALATTR = @Value(y3)
    -> PointConnector
PointConnector
    LINE -> CoordinateExtractor
    LINE -> PointConnector_LINE
PointConnector_LINE: Inspector
CoordinateExtractor
    Y_ATTR = _y1
    X_ATTR = _x1
    Z_DEFAULT = -9999
    Z_ATTR = _z
    IND = 0
    -> CoordinateExtractor_2
CoordinateExtractor_2
    Y_ATTR = _y2
    X_ATTR = _x2
    Z_DEFAULT = -9999
    Z_ATTR = _z
    IND = 1
    -> ExpressionEvaluator1
ExpressionEvaluator1
    VAL_ATTR = rot1
    EXPRESSION = (@atan2((@Value(_y2)-@Value(_y1)),(@Value(_x2)-@Value(_x1))))*180.0/(22/7.0)
    -> FeatureMerger_3 [input 1]
AttributeSplitter_4
    LIST_NAME = _pt2
    ATTR_NAME = _pts{1}
    DELIMITER = ,
    TRIM_OPTION = Both
    DROP_EMPTY_PARTS = No
    -> AttributeCreator_4
AttributeCreator_4
    ATTR_LIST = x4,@Value(_pt2{0}),y4,@Value(_pt2{1})
    -> 2DPointAdder_4
2DPointAdder_4
    XVALATTR = @Value(x4)
    YVALATTR = @Value(y4)
    -> PointConnector_2
PointConnector_2
    LINE -> Reprojector_2
    LINE -> PointConnector_2_LINE
Reprojector_2
    DEST = EPSG:3857
    RASTER_CELL_SIZE = Preserve Cells
    STROKE_ARCS = Yes
    SOURCE = $(SourceCoordinateSystem)
    INTERPOLATION_TYPE_NAME = Nearest Neighbor
    REPROJECTED -> CoordinateExtractor_3
CoordinateExtractor_3
    Y_ATTR = _y1
    X_ATTR = _x1
    Z_DEFAULT = -9999
    Z_ATTR = _z
    IND = 0
    -> CoordinateExtractor_4
CoordinateExtractor_4
    Y_ATTR = _y2
    X_ATTR = _x2
    Z_DEFAULT = -9999
    Z_ATTR = _z
    IND = 1
    -> ExpressionEvaluator2
ExpressionEvaluator2
    VAL_ATTR = rot2
    EXPRESSION = (@atan2((@Value(_y2)-@Value(_y1)),(@Value(_x2)-@Value(_x1))))*180.0/(22/7.0)
    -> FeatureMerger_3 [input 2]
FeatureMerger_3
    PROCESS_DUPS = No
    MERGE_TYPE = Attributes Only
    SUPPLIERS_FIRST = No
    JOIN_KEYS = @Value(WORLD) @Value(WORLD)
    SUPPLIER_PREFIX_DUMMY = YES
    MERGED -> AttributeCreator
AttributeCreator
    ATTR_LIST = CALCROT,@Evaluate(@Value(rot2)-@Value(rot1)),WORLDFILE,@Value(text_line_data)
    -> ExpressionEvaluator_8
ExpressionEvaluator_8
    VAL_ATTR = _angle
    EXPRESSION = @Value(CALCROT) + 90.0
    -> TestFilter_5
TestFilter_5
    TEST_LIST = BOOL_OP,OR,COMPOSITE_TEST,<Unused>,TEST_CLAUSE,"TEST ""@Value(CALCROT)"" > ""180.0""",_angle > 180.0
    DEFAULT_VALUE = <UNFILTERED>
    _angle > 180.0 -> ExpressionEvaluator_10
    <UNFILTERED> -> AttributeRemover
ExpressionEvaluator_10
    VAL_ATTR = _angle
    EXPRESSION = @Value(CALCROT) -180.0
    -> AttributeRemover
AttributeRemover
    REMOVE_ATTRS = text_line_data,x1,y1,x2,y2,x3,y3,x4,y4,rot1,rot2,_list{0},_pt{0},_pt2{0},_list{1},_pt{1},_pt2{1}
    -> OUTPUT (output)
    -> AttributeCreator_OUTPUT
OUTPUT (output)
AttributeCreator_OUTPUT: Inspector
PointConnector_2_LINE: Inspector
Reprojector
    DEST = EPSG:3857
    RASTER_CELL_SIZE = Preserve Cells
    STROKE_ARCS = Yes
    SOURCE = $(SourceCoordinateSystem)
    INTERPOLATION_TYPE_NAME = Nearest Neighbor

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    SCOPE = Local
    START = 0
    DOMAIN = counter
    CNT_ATTR = _selfID
    -> GeometryExtractor
GeometryExtractor
    OGCVERSION = 1.2
    ATTR = _geometry
    KIND_LONG = OGC Well Known Text
    -> SelfIntersector
SelfIntersector
    SEG_ATTR = _segments
    SELF_INTERSECTED -> DuplicateRemover
DuplicateRemover
    KEYATTR = _selfID
    UNIQUE -> TESTER
TESTER: Tester
    TEST_MODE = NUMERIC
    BOOL_OP = OR
    TEST_LIST = &_segments,>,1
    TEST_CLAUSE = TEST @Value(_segments) > 1
    FAILED -> PartCounter_2
    PASSED -> GeometryReplacer
PartCounter_2
    COUNT_ATTR = _part_count2
    RECURSIVE_PARAM = No
    -> TESTER_2
TESTER_2: Tester
    TEST_MODE = Automatic
    BOOL_OP = OR
    TEST_LIST = &_part_count1,=,&_part_count2
    TEST_CLAUSE = TEST @Value(_part_count1) = @Value(_part_count2)
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)

FME custom transformer gzAggregateLines
Clean geometries and Aggregate Floorplan lines into _Optimized features

INPUT (input)
    -> CoordinateCounter
CoordinateCounter
    CNT_ATTR = _coordcount
    -> LengthCalculator_2
LengthCalculator_2
    LEN_ATTR = _length
    MULT = 1
    DIM = 2
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> SelfIntersectChecker
SelfIntersectChecker
    NotSelfIntersecting -> GeometryCoercer
    SelfIntersecting -> SelfIntersector
SelfIntersector
    SEG_ATTR = _segments
    SELF_INTERSECTED -> GeometryCoercer
GeometryCoercer
    KIND = fme_line
    COERCED -> Aggregator_2
Aggregator_2
    GROUP_BY = FACFLOOR
    SEP = ,
    CONTAIN_INDIVID_GEOMS = No
    ACCUM_ATTRS_NAME = Yes
    ORDERED = No
    AGGREGATE -> OUTPUT (output)
OUTPUT (output)
