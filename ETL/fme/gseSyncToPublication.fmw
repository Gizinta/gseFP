FME workspace gseSyncToPublication.fmw

Parameters:
- GEODATABASE_SDE_IN_CONNECTION_FILE_GEODATABASE_SDE = C:\Apps\Gizinta\gseFP\ETL\serverConfig\GIS Production.sde   # Connection File
- GEODATABASE_SDE_OUT_CONNECTION_FILE_GEODATABASE_SDE = C:\Apps\Gizinta\gseFP\ETL\serverConfig\GIS Publication.sde   # Connection File
- DestDataset_GEODATABASE_SDE = sde   # Destination Esri ArcSDE Geodatabase Dataset

Readers:
- GEODATABASE_SDE_1: GEODATABASE_SDE from sde
- GEODATABASE_SDE_2: GEODATABASE_SDE from $(DestDataset_GEODATABASE_SDE)

Writers:
- GEODATABASE_SDE_3: GEODATABASE_SDE to $(DestDataset_GEODATABASE_SDE)
- GEODATABASE_SDE_4: GEODATABASE_SDE to $(DestDataset_GEODATABASE_SDE)

DBO.Floor_Area (reader GEODATABASE_SDE_1)
    attributes: geodb_oid integer, OBJECTID integer, FLOORID char(60), FLOORCODE char(20), FLOORAREA double, NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), SHAPE.STArea() double, SHAPE.STLength() double
    -> ChangeDetector [input 1]
dbo.pubFloor_Areas (reader GEODATABASE_SDE_2)
    attributes: geodb_oid integer, FLOORID char(60), FLOORCODE char(20), FLOORAREA double, NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), OBJECTID integer
    -> ChangeDetector [input 2]
ChangeDetector
    MATCHATTRS = FLOORID FLOORCODE FLOORAREA NAMESHORT NAMELONG SCHELEV GROUNDELEV FLOORLEVEL STACKLEVEL SENSITIVITY CALCROT DDPFLOORSORT BUILDINGID SITEID SOURCEDWG
    MATCH = 3D
    MATCH_STRATEGY = Match Selected Attributes
    LENIENT_MATCH = No
    BLANK_AND_MISSING_DIFFER = Yes
    EXTRA_VERTEX_TOLERANCE = .001
    ADDED -> dbo.Floor_Area (writer GEODATABASE_SDE_3)
    DELETED -> dbo.Floor_Area (writer GEODATABASE_SDE_4)
dbo.Floor_Area (writer GEODATABASE_SDE_3)
    attributes: geodb_oid integer, OBJECTID integer, FLOORID char(50), BUILDINGID char(50), SOURCEDWG char(50), SHAPE.STArea() double, SHAPE.STLength() double
dbo.Floor_Area (writer GEODATABASE_SDE_4)
    attributes: geodb_oid integer, OBJECTID integer, FLOORID char(50), BUILDINGID char(50), SOURCEDWG char(50), SHAPE.STArea() double, SHAPE.STLength() double
DBO.Floor_Outline (reader GEODATABASE_SDE_1)
    attributes: geodb_oid integer, OBJECTID integer, FLOORID char(60), FLOORCODE char(20), NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), SHAPE.STArea() double, SHAPE.STLength() double
    -> ChangeDetector_2 [input 1]
dbo.pubFloor_Outlines (reader GEODATABASE_SDE_2)
    attributes: geodb_oid integer, FLOORID char(60), FLOORCODE char(20), NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), OBJECTID integer
    -> ChangeDetector_2 [input 2]
ChangeDetector_2
    MATCHATTRS = FLOORID FLOORCODE NAMESHORT NAMELONG SCHELEV GROUNDELEV FLOORLEVEL STACKLEVEL SENSITIVITY CALCROT DDPFLOORSORT BUILDINGID SITEID SOURCEDWG
    MATCH = 3D
    MATCH_STRATEGY = Match Selected Attributes
    LENIENT_MATCH = No
    BLANK_AND_MISSING_DIFFER = Yes
    ADDED -> DBO.Floor_Outline (writer GEODATABASE_SDE_3)
    DELETED -> DBO.Floor_Outline (writer GEODATABASE_SDE_4)
DBO.Floor_Outline (writer GEODATABASE_SDE_3)
    attributes: geodb_oid integer, OBJECTID integer, FLOORID char(60), FLOORCODE char(20), NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), SHAPE.STArea() double, SHAPE.STLength() double
DBO.Floor_Outline (writer GEODATABASE_SDE_4)
    attributes: geodb_oid integer, OBJECTID integer, FLOORID char(60), FLOORCODE char(20), NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), SHAPE.STArea() double, SHAPE.STLength() double
DBO.Floor_Point (reader GEODATABASE_SDE_1)
    attributes: geodb_oid integer, OBJECTID integer, FLOORCODE char(20), FLOORID char(60), NAMESHORT char(50), NAMELONG char(100), SCHELEV integer, GROUNDELEV double, FLOORLEVEL integer, STACKLEVEL double, SENSITIVITY char(20), CALCROT double, INTERIORSPACECOUNT integer, FLOORPLANLINECOUNT integer, FLOORAREACOUNT integer, MODPORTRAIT double, MODLANDSCAPE double, SCALE11X17 double, DDPFLOORSORT char(61), SITEID char(60), BUILDINGID char(60), LASTUPDATE date, LASTEDITOR char(30), SCALE85X11 double
    -> ChangeDetector_3 [input 1]
dbo.pubFloor_Points (reader GEODATABASE_SDE_2)
    attributes: geodb_oid integer, FLOORCODE char(20), FLOORID char(60), NAMESHORT char(50), NAMELONG char(100), SCHELEV integer, GROUNDELEV double, FLOORLEVEL integer, STACKLEVEL double, SENSITIVITY char(20), CALCROT double, INTERIORSPACECOUNT integer, FLOORPLANLINECOUNT integer, FLOORAREACOUNT integer, MODPORTRAIT double, MODLANDSCAPE double, DDPFLOORSORT char(61), SITEID char(60), BUILDINGID char(60), LASTUPDATE date, LASTEDITOR char(30), OBJECTID integer, SCALE85X11 double, SCALE11X17 double
    -> DuplicateRemover_2
DuplicateRemover_2
    KEYATTR = FLOORID
    UNIQUE -> ChangeDetector_3 [input 2]
Note: no geometry comparison
ChangeDetector_3
    MATCHATTRS = FLOORCODE FLOORID NAMESHORT NAMELONG SCHELEV GROUNDELEV FLOORLEVEL STACKLEVEL SENSITIVITY CALCROT MODPORTRAIT MODLANDSCAPE DDPFLOORSORT SITEID BUILDINGID
    MATCH = 3D
    MATCH_STRATEGY = Match Selected Attributes
    LENIENT_MATCH = No
    BLANK_AND_MISSING_DIFFER = No
    ADDED -> DBO.Floor_Point (writer GEODATABASE_SDE_3)
    DELETED -> DBO.Floor_Point (writer GEODATABASE_SDE_4)
DBO.Floor_Point (writer GEODATABASE_SDE_3)
    attributes: geodb_oid integer, OBJECTID integer, FLOORCODE char(20), FLOORID char(60), NAMESHORT char(50), NAMELONG char(100), SCHELEV integer, GROUNDELEV double, FLOORLEVEL integer, STACKLEVEL double, SENSITIVITY char(20), CALCROT double, INTERIORSPACECOUNT integer, FLOORPLANLINECOUNT integer, FLOORAREACOUNT integer, MODPORTRAIT double, MODLANDSCAPE double, SCALE85X11 double, SCALE11X17 double, DDPFLOORSORT char(61), SITEID char(60), BUILDINGID char(60), LASTUPDATE date, LASTEDITOR char(30)
DBO.Floor_Point (writer GEODATABASE_SDE_4)
    attributes: geodb_oid integer, OBJECTID integer, FLOORCODE char(20), FLOORID char(60), NAMESHORT char(50), NAMELONG char(100), SCHELEV integer, GROUNDELEV double, FLOORLEVEL integer, STACKLEVEL double, SENSITIVITY char(20), CALCROT double, INTERIORSPACECOUNT integer, FLOORPLANLINECOUNT integer, FLOORAREACOUNT integer, MODPORTRAIT double, MODLANDSCAPE double, SCALE85X11 double, SCALE11X17 double, DDPFLOORSORT char(61), SITEID char(60), BUILDINGID char(60), LASTUPDATE date, LASTEDITOR char(30)
DBO.FloorplanLine (reader GEODATABASE_SDE_1)
    attributes: geodb_oid integer, OBJECTID integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), SHAPE.STLength() double
    -> ChangeDetector_4 [input 1]
dbo.pubFloorplanLines (reader GEODATABASE_SDE_2)
    attributes: geodb_oid integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), OBJECTID integer
    -> ChangeDetector_4 [input 2]
Note: Floor + Source layer for IDs
ChangeDetector_4
    MATCHATTRS = FLOORID FLOORCODE NAMESHORT NAMELONG SCHELEV GROUNDELEV FLOORLEVEL STACKLEVEL SENSITIVITY SITEID BUILDINGID SOURCELAYER SOURCEID SOURCEDWG
    MATCH = 3D
    MATCH_STRATEGY = Match Selected Attributes
    LENIENT_MATCH = No
    BLANK_AND_MISSING_DIFFER = Yes
    ADDED -> DBO.FloorplanLine (writer GEODATABASE_SDE_3)
    DELETED -> DBO.FloorplanLine (writer GEODATABASE_SDE_4)
DBO.FloorplanLine (writer GEODATABASE_SDE_3)
    attributes: geodb_oid integer, OBJECTID integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), SHAPE.STLength() double
DBO.FloorplanLine (writer GEODATABASE_SDE_4)
    attributes: geodb_oid integer, OBJECTID integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), SHAPE.STLength() double
DBO.InteriorSpace (reader GEODATABASE_SDE_1)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), SPACECLASS char(60), SPACEAREA double, BUILDINGID char(60), SITEID char(60), SOURCEID char(30), SOURCEDWG char(60), LASTUPDATE date, LASTEDITOR char(30), SHAPE.STArea() double, SHAPE.STLength() double
    -> ChangeDetector_5 [input 1]
dbo.pubInteriorSpaces (reader GEODATABASE_SDE_2)
    attributes: geodb_oid integer, SPACEID char(60), ROOMNUMBER char(30), FLOORID char(60), FLOORCODE char(20), NAMESHORT char(50), NAMELONG char(100), SCHELEV integer, GROUNDELEV double, FLOORLEVEL integer, STACKLEVEL double, SENSITIVITY char(20), SpaceClass char(60), SpaceArea double, BUILDINGID char(60), SITEID char(60), SOURCEID char(30), SOURCEDWG char(60), LASTUPDATE date, LASTEDITOR char(30), OBJECTID integer
    -> ChangeDetector_5 [input 2]
ChangeDetector_5
    MATCHATTRS = SPACEID ROOMNUMBER FLOORID FLOORCODE NAMESHORT NAMELONG SCHELEV GROUNDELEV FLOORLEVEL STACKLEVEL SENSITIVITY BUILDINGID SITEID SOURCEDWG
    MATCH = 3D
    MATCH_STRATEGY = Match Selected Attributes
    LENIENT_MATCH = No
    BLANK_AND_MISSING_DIFFER = Yes
    ADDED -> DBO.InteriorSpace (writer GEODATABASE_SDE_3)
    DELETED -> DBO.InteriorSpace (writer GEODATABASE_SDE_4)
DBO.InteriorSpace (writer GEODATABASE_SDE_3)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), SPACECLASS char(60), SPACEAREA double, BUILDINGID char(60), SITEID char(60), SOURCEID char(30), SOURCEDWG char(60), LASTUPDATE date, LASTEDITOR char(30), SHAPE.STArea() double, SHAPE.STLength() double
DBO.InteriorSpace (writer GEODATABASE_SDE_4)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), SPACECLASS char(60), SPACEAREA double, BUILDINGID char(60), SITEID char(60), SOURCEID char(30), SOURCEDWG char(60), LASTUPDATE date, LASTEDITOR char(30), SHAPE.STArea() double, SHAPE.STLength() double
DBO.InteriorSpace_Tilt (reader GEODATABASE_SDE_1)
    attributes: geodb_oid integer, OBJECTID integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), SHAPE.STArea() double, SHAPE.STLength() double
    -> ChangeDetector_6 [input 1]
dbo.pubInteriorSpaces_Tilt (reader GEODATABASE_SDE_2)
    attributes: geodb_oid integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), OBJECTID integer
    -> ChangeDetector_6 [input 2]
ChangeDetector_6
    MATCHATTRS = SPACEID ROOMNUMBER FLOORID FLOORCODE NAMESHORT NAMELONG FLOORLEVEL STACKLEVEL SENSITIVITY BUILDINGID SITEID
    MATCH = 3D
    MATCH_STRATEGY = Match Selected Attributes
    LENIENT_MATCH = No
    BLANK_AND_MISSING_DIFFER = Yes
    ADDED -> DBO.InteriorSpace_Tilt (writer GEODATABASE_SDE_3)
    DELETED -> DBO.InteriorSpace_Tilt (writer GEODATABASE_SDE_4)
DBO.InteriorSpace_Tilt (writer GEODATABASE_SDE_3)
    attributes: geodb_oid integer, OBJECTID integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), SHAPE.STArea() double, SHAPE.STLength() double
DBO.InteriorSpace_Tilt (writer GEODATABASE_SDE_4)
    attributes: geodb_oid integer, OBJECTID integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), SHAPE.STArea() double, SHAPE.STLength() double
dbo.pubInteriorSpace_Points (reader GEODATABASE_SDE_2)
    attributes: geodb_oid integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30), OBJECTID integer
    -> ChangeDetector_7 [input 2]
DBO.InteriorSpace_Point (reader GEODATABASE_SDE_1)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30)
    -> ChangeDetector_7 [input 1]
ChangeDetector_7
    MATCHATTRS = SPACEID ROOMNUMBER FLOORID FLOORCODE NAMESHORT NAMELONG FLOORLEVEL STACKLEVEL SENSITIVITY BUILDINGID SITEID
    MATCH = 3D
    MATCH_STRATEGY = Match Selected Attributes
    LENIENT_MATCH = No
    BLANK_AND_MISSING_DIFFER = Yes
    ADDED -> DBO.InteriorSpace_Point (writer GEODATABASE_SDE_3)
    DELETED -> DBO.InteriorSpace_Point (writer GEODATABASE_SDE_4)
DBO.InteriorSpace_Point (writer GEODATABASE_SDE_3)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30)
DBO.InteriorSpace_Point (writer GEODATABASE_SDE_4)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30)
